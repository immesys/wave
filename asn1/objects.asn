WAVE-Schema DEFINITIONS ::=
BEGIN

  -- When saved in a file or sent over the wire, wrap the object with a
  -- type identifier
  WaveWireObject ::= INSTANCE OF TYPE-IDENTIFIER ({WaveObjects})

  -- A set of policy statements about an Entity, potentially granting
  -- permissions or establishing facts
  WaveAttestation ::= SEQUENCE {
    tbs SEQUENCE {
      -- the subject of the attestation, who is receiving permissions or
      -- having a property attested to
      subject EntityHash,
      subjectLocation Location,

      -- how this attestation revoked
      revocations SEQUENCE OF RevocationOption,
      -- extensions that are visible without any decryption of the
      -- attestation
      publicExtensions SEQUENCE OF Extension,
      -- The main content of the attestation SHOULD be encrypted using
      -- a scheme that permits provers and verifiers to decrypt it but
      -- nobody else. The result of decrypting this MUST be an
      -- AttestationBody object but depending on the context of the
      -- decryption (e.g prover vs verifier) the contents of that
      -- AttestationBody object may differ.
      body INSTANCE OF TYPE-IDENTIFIER ({AttestationBodySchemes})
    },
    -- The attestation is signed with an ephemeral signing key generated
    -- for a single use (or another signature scheme suitable for single
    -- use is permitted). The details of this signature are bound to
    -- the real attestation key inside the body but we don't reveal the
    -- attester at this layer
    outerSignature INSTANCE OF TYPE-IDENTIFIER ({OuterSignatureSchemes})
  }


  -- An arbitrary message encrypted using WAVE
  WaveEncryptedMessage ::= SEQUENCE {
    -- content: arbitrary message contents
    -- encryption algorithm: AES128
    -- key: contentsKey
    contents OCTET STRING,

    -- encrypted forms of contentsKey
    keys SEQUENCE OF E2EEMessageKey,

    -- Additional extension fields
    extensions SEQUENCE OF Extension
  }

  E2EEMessageKey ::= INSTANCE OF TYPE-IDENTIFIER ({E2EEMessageKeySchemes})

  -- Irrespective of the algorithm used to encrypt the body, this
  -- is the object it contains
  AttestationBody ::= SEQUENCE {

    -- These are fields visible to both prover and verifier
    verifierBody AttestationVerifierBody,

    -- Material relating to the policy scheme that is only visible
    -- to the prover. When decoding as a verifier, this should not be
    -- visible
    proverPolicyAddendums SEQUENCE OF PolicyAddendum,

    -- These are fields that contain information that should be
    -- visible to the subject of the Attestation (and perhaps
    -- chained attestation subjects) but should not be visible to those
    -- verifying this attestation as part of a proof.
    proverExtensions SEQUENCE OF Extension

  }

  PolicyAddendum ::= INSTANCE OF TYPE-IDENTIFIER ({PolicyAddendumSchemes})

  -- These are fields visible to both prover and verifier
  AttestationVerifierBody ::= SEQUENCE {
    -- the creator of the DOT
    attester EntityHash,
    attesterLocation Location,

    -- the subject of the attestation, in outside...
    -- subject EntityHash,

    -- the policy domain. If omitted, the policy is global. A policy domain
    -- is an Entity that represents the scope of the attestation. The exact
    -- semantics are specific to the scheme, but there may be cross-policy
    -- behavior associated with the domain (e.g WR1 restricts visibility of
    -- attribute sets to those already having some grant in the domain).
    -- in some policy schemes the domain is the root of trust
    -- domain EntityHash OPTIONAL,

    -- the visibility partition. The exact semantics are specific to the
    -- scheme but there may be some cross-policy behavior associated
    -- with the partition (e.g WR1 only allows the verifier body to
    -- be decrypted by those having the key associated with the Partition
    -- or some subkey). If the sequence is length zero,
    -- partition SEQUENCE OF OCTET STRING,

    -- when is this trust valid
    validity SEQUENCE {
      notBefore UTCTime,
      notAfter UTCTime
    },

    -- the nature of the trust
    policy INSTANCE OF TYPE-IDENTIFIER ({PolicySchemes}),

    -- extensions for use by the verifier
    extensions SEQUENCE OF Extension,

    -- binding that proves that the outer signature is made by the same
    -- key that the source used (the ephemeral keys have not been switched)
    outerSignatureBinding INSTANCE OF TYPE-IDENTIFIER ({OuterSignatureBindingSchemes})
  }

  Extension ::= SEQUENCE {
    extnID OBJECT IDENTIFIER,
    -- should parsing of the object fail if this extension is not understood
    critical BOOLEAN,
    -- DER encoding of ASN.1 value identified by extnID
    value OCTET STRING
  }

  RevocationOption ::= SEQUENCE {
    -- If this revocation scheme is not understood, should
    -- the object be treated as revoked (TRUE) or not (FALSE)
    critical BOOLEAN,
    scheme INSTANCE OF TYPE-IDENTIFIER ({RevocationSchemes})
  }

  WaveEntity ::= SEQUENCE {
    tbs SEQUENCE {
      -- the canonical certification and attestation key. This is what is used
      -- to sign attestation outerSignatureBindings, and to sign this object
      verifyingKey EntityPublicKey,
      -- other public keys
      keys SEQUENCE OF EntityPublicKey,
      -- when is this entity valid
      validity SEQUENCE {
        notBefore UTCTime,
        notAfter UTCTime
      },
      -- revocations
      revocations SEQUENCE OF RevocationOption,
      -- extensions
      extensions SEQUENCE OF Extension
    },
    -- the algorithm is determined by the type of
    -- verifyingKey
    signature OCTET STRING
  }

  WaveEntitySecret ::= SEQUENCE {
    entity WaveEntity,

    keyring INSTANCE OF TYPE-IDENTIFIER ({EntityKeyringSchemes})
  }

  EntityKeyring ::= SEQUENCE {
    keys SEQUENCE OF EntityKeyringEntry
  }

  EntityKeyringEntry ::= SEQUENCE {
    public EntityPublicKey,
    secret EntityPrivateKey
  }

  BLS12381OAQUEKeyringBundle ::= SEQUENCE {
    params Params-BLS12381-OAQUE,
    entries SEQUENCE OF BLS12381OAQUEBundleEntry
  }

  BLS12381OAQUEBundleEntry ::= SEQUENCE {
    partitionChange SEQUENCE OF SEQUENCE {
      index INTEGER,
      content OCTET STRING
    },
    key Private-BLS12381-OAQUE
  }

  EntityPrivateKey ::= INSTANCE OF TYPE-IDENTIFIER ({EntitySecretKeySchemes})

  EntityPublicKey ::= SEQUENCE {
    capabilityFlags SET OF Capability,
    key INSTANCE OF TYPE-IDENTIFIER ({EntityKeySchemes})
  }

  Capability ::= INTEGER {
    -- signing other keys
    certification      (1),
    -- signing attestations
    attestation        (2),
    -- signing messages or other content
    signing            (3),
    -- signing challenges that reveal ID
    authentication     (4),
    -- signing challenges that prove authorization (not via identity)
    authorization      (5),
    --
    encryption         (6)
  }

  -- there are different kinds of proofs, this represents just one, the
  -- explicit proof that reveals the attestations. The final authorization
  -- or truth conveyed is the union of the paths through the given set of
  -- attestations
  WaveExplicitProof ::= SEQUENCE {
    attestations SEQUENCE OF AttestationReference,
    -- this is a chain of attestations connected end-to-end
    -- that represent a path through the subset of the authorization
    -- graph given in the attestations field. The integer references
    -- an attestation inside the parent object
    paths SEQUENCE OF SEQUENCE OF INTEGER,
    -- optionally, entities the sender thinks the receiver won't be
    -- able to resolve can be included here (DER encoded)
    entities SEQUENCE OF OCTET STRING,
    extensions SEQUENCE OF Extension
  }



  AttestationReference ::= SEQUENCE {
    -- the hash of the WaveAttestation
    hash AttestationHash,

    -- generally the attestation is put in here verbatim
    content [0] OCTET STRING OPTIONAL,

    -- or a location is given that permits retrieving the attestation
    location [1] SEQUENCE OF Location,

    -- the content will generally need some keys to decrypt
    keys [2] SEQUENCE OF AttestationVerifierKey,

    -- for some revocation schemes, it may be necessary to submit
    -- additional information with the attestation reference that shows
    -- that the attestation is not revoked (such as a signed object by
    -- the locations in the revocation option)
    revocationChecks [3] SEQUENCE OF RevocationCheck,

    extensions [4] SEQUENCE OF Extension
  }

  RTreePolicy ::= SEQUENCE {
    -- the namespace, common to all statements. This also becomes the
    -- WR1 domain for visibility control if wr1 is used
    namespace EntityHash,
    namespaceLocation Location,
    -- specifically for use with WR1, this controls who can see the
    -- attestation
    -- this is a virtual field, there must exist some function
    -- partition but we don't store the partition
    -- partition SEQUENCE OF OCTET STRING OPTIONAL,

    -- Similar to bosswave TTL, how many times can this be redelegated
    indirections INTEGER,
    statements SEQUENCE OF RTreeStatement
  }

  RTreeStatement ::= SEQUENCE {
    permissionSet EntityHash,
    permissions SEQUENCE OF UTF8String,
    resource UTF8String,
    comment UTF8String OPTIONAL
  }

  -- A key specifically to enable a verifier to inspect a subset of an attestation
  -- for the purposes of verifying a proof
  AttestationVerifierKey ::= INSTANCE OF TYPE-IDENTIFIER ({AttestationVerifierKeySchemes})

  -- A mini proof that a revocation does not exist
  RevocationCheck ::= INSTANCE OF TYPE-IDENTIFIER ({RevocationCheckSchemes})


  Hash ::= INSTANCE OF TYPE-IDENTIFIER ({HashSchemes})
  EntityHash ::= Hash
  AttestationHash ::= Hash
  -- The three currently supported hash schemes
  HashSha3-256 ::= OCTET STRING
  HashSha-256 ::= OCTET STRING
  HashKeccak-256 ::= OCTET STRING

  -- When referencing an attestation or entity hash, where should this be
  -- resolvable
  Location ::= INSTANCE OF TYPE-IDENTIFIER ({LocationSchemes})

  -- this object will be DER encoded and present in the location.value scheme
  -- when the scheme is location-scheme-url
  LocationURL ::= SEQUENCE {
    value UTF8String,
    apiVersion INTEGER
  }

  -- this object will be DER encoded and present in the location.value scheme
  -- when the scheme is location-scheme-ethereum-blockchain
  LocationEthereum ::= SEQUENCE {
    chainID INTEGER,
    contractAddress INTEGER
  }

  -- A pre-shared-key attestation body ciphertext
  PSKBodyCiphertext ::= SEQUENCE {
    -- when decrypted results in the DER of an AttestationBody
    attestationBodyCiphertext OCTET STRING,
    -- the key used for encryption (which also conveys the scheme)
    encryptedUnder  EntityPublicKey
  }

  WaveNameDeclaration ::= SEQUENCE {
    tbs SEQUENCE {
      attester EntityHash,
      attesterLocation Location,
      revocations SEQUENCE OF RevocationOption,
      publicExtensions SEQUENCE OF Extension,
      -- content: NameDeclarationBody
      -- encryption algorithm: AES128
      -- encryption key: bodyKey
      body OCTET STRING,
      keys SEQUENCE OF NameDeclarationKey
    },
    signature OCTET STRING
  }

  NameDeclarationKey ::= INSTANCE OF TYPE-IDENTIFIER ({NameDeclarationKeySchemes})

  NameDeclarationBody ::= SEQUENCE {
    name UTF8String,
    subject EntityHash,
    subjectLocation Location,
    validity SEQUENCE {
      notBefore UTCTime,
      notAfter UTCTime
    },
    privateExtensions SEQUENCE OF Extension
  }

  -- empty sequence, the body is then just DER encoded
  NameDeclarationKeyNone ::= SEQUENCE {

  }

  NameDeclarationKeyWR1 ::= SEQUENCE {
    -- content: MessageKeyWR1Envelope DER encoded
    -- encryption algorithm: AES128
    -- encryption key: envelopeKey
    envelope OCTET STRING,

    -- content envelopeKey
    -- encryption algorithm: IBE-BLS12381 in declaration namespace system
    -- id: envelopeID (namespace)
    envelopeKey-ibe-BLS12381 OCTET STRING,

    namespace EntityHash,
    namespaceLocation Location
  }

  NameDeclarationWR1Envelope ::= SEQUENCE {
    partition SEQUENCE OF OCTET STRING,
    -- content: bodyKey
    -- encryption algorithm: oaque-BLS12381
    -- encryption id: partition
    bodyKey OCTET STRING
  }

  -- A body ciphertext for the wave reference 1 scheme
  WR1BodyCiphertext ::= SEQUENCE {
    -- content: WR1VerifierBody DER encoded
    -- encryption algorithm: AES128
    -- key: verifierBodyKey
    verifierBodyCiphertext OCTET STRING,

    -- content: WR1ProverBody DER encoded
    -- encryption algorithm: AES128
    -- key: proverBodyKey
    proverBodyCiphertext OCTET STRING,

    -- content WR1Envelope DER encoded
    -- encryption algorithm: AES128
    -- key: envelopeKey
    envelopeCiphertext OCTET STRING,

    -- content envelopeBodyKey
    -- encryption algorithm: IBE-BLS12381 in subject system
    -- id: envelopeID (namespace)
    envelopeKey-ibe-BLS12381 OCTET STRING,

    -- content envelopeBodyKey
    -- encryption algorithm: AES128
    -- key: ECDH (outer signature key, subject key)
    -- this permits reading the envelope if you are the direct
    -- recipient, even without knowing the namespace
    envelopeKey-curve25519 OCTET STRING,

    -- content prover/verifierBodyKeys
    -- encryption algorithm: AES128
    -- key: ECDH (outer signature key, attester key)
    -- this permits reading the attestation if you are the attester
    -- even without knowing the namespace
    envelopeKey-curve25519-attester OCTET STRING
  }

  WR1Envelope ::= SEQUENCE {
    -- content: proverBodyKey || proverBodyNonce || verifierBodyKey || verifierBodyNonce
    -- encryption algorithm: oaque-BLS12381 in subject system
    -- encryption attribute set: Partition
    bodyKeys-oaque OCTET STRING,

    -- the attribute set for the verifierBodyKey-oaque ciphertext
    partition SEQUENCE OF OCTET STRING
  }

  WR1ProverBody ::= SEQUENCE {
    --which keys do we give other people
    --we have PartitionKeys that reveal the content
    --we have a Domain Key that reveals the partition attribute set
    addendums SEQUENCE OF PolicyAddendum,

    extensions SEQUENCE OF Extension
  }

  WR1VerifierBody ::= SEQUENCE {
    attestationVerifierBody AttestationVerifierBody
  }

  Ed25519OuterSignature ::= SEQUENCE {
    verifyingKey OCTET STRING,
    signature OCTET STRING
  }

  Signature ::= SEQUENCE {
    -- use the key scheme as an identifier
    scheme OBJECT IDENTIFIER,
    signature OCTET STRING
  }

  SignedOuterKey ::= SEQUENCE {
    tbs SEQUENCE {
      outerSignatureScheme OBJECT IDENTIFIER,
      verifyingKey OCTET STRING
    },
    signature OCTET STRING
  }

  TrustLevel ::= SEQUENCE {
    trust INTEGER (1..4)
  }

  CommitmentRevocationOption ::= SEQUENCE {
    -- What the commitment should hash to
    hash Hash,
    -- Where to look for it
    location Location
  }

  AVKeyAES128-GCM ::= OCTET STRING

  Private-Ed25519 ::= OCTET STRING
  Private-Curve25519 ::= OCTET STRING
  Private-BLS12381-OAQUE ::= OCTET STRING
  Private-BLS12381-IBE ::= OCTET STRING
  Master-BLS12381-OAQUE ::= OCTET STRING
  Master-BLS12381-IBE ::= OCTET STRING
  Public-Ed25519 ::= OCTET STRING
  Public-Curve25519 ::= OCTET STRING
  Public-OAQUE ::= SEQUENCE {
    params Params-BLS12381-OAQUE,
    attributeset SEQUENCE OF OCTET STRING
  }
  Params-BLS12381-OAQUE ::= OCTET STRING
  Params-BLS12381-IBE ::= OCTET STRING
  Public-BLS12381-IBE ::= SEQUENCE {
    params Params-BLS12381-IBE,
    id OCTET STRING
  }
  -- Encapsulates parameters to PBKDF2. Sha3-512 is assumed as the hash function
  -- in this particular scheme
  KeyringAESCiphertext ::= SEQUENCE {
    ciphertext OCTET STRING,
    salt OCTET STRING,
    iterations INTEGER
  }

  MessageKeyCurve25519ECDH ::= SEQUENCE {
    ciphertext OCTET STRING
  }

  MessageKeyWR1 ::= SEQUENCE {
    -- content: MessageKeyWR1Envelope DER encoded
    -- encryption algorithm: AES128
    -- encryption key: envelopeKey
    envelope OCTET STRING,

    -- content envelopeKey
    -- encryption algorithm: IBE-BLS12381 in message namespace system
    -- id: envelopeID (namespace)
    envelopeKey-ibe-BLS12381 OCTET STRING,

    -- the system for the keys
    namespace EntityHash,
    namespaceLocation Location
  }

  MessageKeyWR1Envelope ::= SEQUENCE {
    partition SEQUENCE OF OCTET STRING,
    -- content: contentsKey
    -- encryption algorithm: oaque-BLS12381
    -- encryption id: partition,
    contentsKey OCTET STRING
  }
--------------------------------------------------------------------------------
-- Universal OIDs
--------------------------------------------------------------------------------
wave-id OBJECT IDENTIFIER ::= { 1 3 6 1 4 1 51157 }

-- Wave object types
--------------------------------------------------------------------------------
wave-object OBJECT IDENTIFIER ::= { wave-id 2 }
attestation-id OBJECT IDENTIFIER ::= { wave-object 1 }
entity-id OBJECT IDENTIFIER ::= { wave-object 2 }
explicit-proof-id OBJECT IDENTIFIER ::= { wave-object 3 }
entity-secret-id OBJECT IDENTIFIER ::= { wave-object 4 }
wave-encrypted-message-id OBJECT IDENTIFIER ::= { wave-object 5 }
wave-name-declaration-id OBJECT IDENTIFIER ::= { wave-object 6 }
WaveObjects TYPE-IDENTIFIER ::= {
  {WaveAttestation IDENTIFIED BY attestation-id} |
  {WaveEntity IDENTIFIED BY entity-id} |
  {WaveExplicitProof IDENTIFIED BY explicit-proof-id} |
  {WaveEntitySecret IDENTIFIED BY entity-secret-id} |
  {WaveEncryptedMessage IDENTIFIED BY wave-encrypted-message-id} |
  {WaveNameDeclaration IDENTIFIED BY wave-name-declaration-id},
...
}

-- Attestation body schemes
--------------------------------------------------------------------------------
attestation-body-scheme OBJECT IDENTIFIER ::= { wave-id 3 }
-- the body is included directly
unencrypted-body-scheme OBJECT IDENTIFIER ::= { attestation-body-scheme 1 }
-- the body is decrypted using the Wave Reference 1 scheme
wr1-body-scheme-v1 OBJECT IDENTIFIER ::= { attestation-body-scheme 2 }
-- the body is decrypted using some pre shared key. This is mostly
-- to force implementations not to be too tied to a specific body scheme
-- which would hinder future development of new body schemes
psk-body-scheme OBJECT IDENTIFIER ::= { attestation-body-scheme 3 }
AttestationBodySchemes TYPE-IDENTIFIER ::= {
 {AttestationBody IDENTIFIED BY unencrypted-body-scheme} |
 {WR1BodyCiphertext IDENTIFIED BY wr1-body-scheme-v1} |
 {PSKBodyCiphertext IDENTIFIED BY psk-body-scheme},
 ...
}

-- Attestation Verifier Key Schemes
--------------------------------------------------------------------------------
attestation-verifier-key-scheme OBJECT IDENTIFIER ::= { wave-id 4 }
attestation-verifier-key-aes128-gcm OBJECT IDENTIFIER ::= { attestation-verifier-key-scheme 1 }
AttestationVerifierKeySchemes TYPE-IDENTIFIER ::= {
 {AVKeyAES128-GCM IDENTIFIED BY attestation-verifier-key-aes128-gcm},
 ...
}

-- Outer signature schemes
--------------------------------------------------------------------------------
outer-signature-scheme OBJECT IDENTIFIER ::= { wave-id 5 }
ephemeral-ed25519 OBJECT IDENTIFIER ::= { outer-signature-scheme 1 }
OuterSignatureSchemes TYPE-IDENTIFIER ::= {
 {Ed25519OuterSignature IDENTIFIED BY ephemeral-ed25519},
 ...
}



-- Outer signature binding schemes
--------------------------------------------------------------------------------
outer-signature-binding-scheme OBJECT IDENTIFIER ::= { wave-id 6 }
signed-outer-key OBJECT IDENTIFIER ::= { outer-signature-binding-scheme 1 }
OuterSignatureBindingSchemes TYPE-IDENTIFIER ::= {
 {SignedOuterKey IDENTIFIED BY signed-outer-key},
 ...
}

-- Revocation check schemes
--------------------------------------------------------------------------------
revocation-check-schemes OBJECT IDENTIFIER ::= { wave-id 7 }
RevocationCheckSchemes TYPE-IDENTIFIER ::= {
  ...
}

-- Location schemes
--------------------------------------------------------------------------------
location-scheme OBJECT IDENTIFIER ::= { wave-id 8 }
location-url-id OBJECT IDENTIFIER ::= { location-scheme 1 }
location-ethereum-v1-id OBJECT IDENTIFIER ::= { location-scheme 2 }
LocationSchemes TYPE-IDENTIFIER ::= {
  {LocationURL IDENTIFIED BY location-url-id} |
  {LocationEthereum IDENTIFIED BY location-ethereum-v1-id},
  ...
}

-- Hash schemes
--------------------------------------------------------------------------------
hash-scheme OBJECT IDENTIFIER ::= { wave-id 9 }
sha3-256-id OBJECT IDENTIFIER ::= { hash-scheme 1 }
keccak-256-id OBJECT IDENTIFIER ::= { hash-scheme 2 }
sha-256-id OBJECT IDENTIFIER ::= { hash-scheme 3 }
HashSchemes TYPE-IDENTIFIER ::= {
  {HashSha3-256 IDENTIFIED BY sha3-256-id} |
  {HashKeccak-256 IDENTIFIED BY keccak-256-id} |
  {HashSha-256 IDENTIFIED BY sha-256-id},
  ...
}

-- Revocation option schemes
--------------------------------------------------------------------------------
revocation-scheme OBJECT IDENTIFIER ::= { wave-id 10 }
commitment-revocation-id OBJECT IDENTIFIER ::= { revocation-scheme 1 }
RevocationSchemes TYPE-IDENTIFIER ::= {
  {CommitmentRevocationOption IDENTIFIED BY commitment-revocation-id},
  ...
}


-- Entity public key schemes
--------------------------------------------------------------------------------
entity-key-scheme OBJECT IDENTIFIER ::= { wave-id 11 }
ed25519-id OBJECT IDENTIFIER ::= { entity-key-scheme 1 }
curve25519-id OBJECT IDENTIFIER ::= { entity-key-scheme 2 }
--  3 through 6 for deprecated BN256 keys
oaque-BLS12381-s20-attributeset-id OBJECT IDENTIFIER ::= { entity-key-scheme 7 }
oaque-BLS12381-s20-params-id OBJECT IDENTIFIER ::= { entity-key-scheme 8 }
ibe-BLS12381-params-id OBJECT IDENTIFIER ::= { entity-key-scheme 9 }
ibe-BLS12381-public-id OBJECT IDENTIFIER ::= { entity-key-scheme 10 }
EntityKeySchemes TYPE-IDENTIFIER ::= {
  {Public-Ed25519 IDENTIFIED BY ed25519-id} |
  {Public-Curve25519 IDENTIFIED BY curve25519-id} |
  {Public-OAQUE IDENTIFIED BY oaque-BLS12381-s20-attributeset-id} |
  {Params-BLS12381-OAQUE IDENTIFIED BY oaque-BLS12381-s20-params-id} |
  {Params-BLS12381-IBE  IDENTIFIED BY ibe-BLS12381-params-id} |
  {Public-BLS12381-IBE IDENTIFIED BY ibe-BLS12381-public-id},
  ...
}

-- Policy schemes
--------------------------------------------------------------------------------
policy-scheme OBJECT IDENTIFIER ::= { wave-id 12 }
trust-level OBJECT IDENTIFIER ::= { policy-scheme 1 }
resource-tree OBJECT IDENTIFIER ::= { policy-scheme 2 }
PolicySchemes TYPE-IDENTIFIER ::= {
  {TrustLevel IDENTIFIED BY trust-level} |
  {RTreePolicy IDENTIFIED BY resource-tree},
  ...
}

-- Policy addendum schemes
--------------------------------------------------------------------------------
policy-addendum-scheme OBJECT IDENTIFIER ::= { wave-id 13 }
-- this key permits the recipient to view the attribute set corresponding
-- to the partition key that would decrypt the attestation body for all
-- attestations in the same visibility domain
wr1-domain-visibility-key OBJECT IDENTIFIER ::= { policy-addendum-scheme 6 }
-- this key permits decrypting attestations where the partition is
-- more qualified than the given key
wr1-partition-key OBJECT IDENTIFIER ::= { policy-addendum-scheme 7 }

-- skip 3, it used to be encryption key

-- this key permits decrypting messages encrypted using OAQUE range
-- keys (like expiry). It is a family of multiple keys
-- 4 reserved for bn256 bundle key
wr1-oaque-bundle-key OBJECT IDENTIFIER ::= { policy-addendum-scheme 5 }

PolicyAddendumSchemes TYPE-IDENTIFIER ::= {
  {EntityKeyringEntry IDENTIFIED BY wr1-domain-visibility-key} |
  {EntityKeyringEntry IDENTIFIED BY wr1-partition-key} |
  {BLS12381OAQUEKeyringBundle IDENTIFIED BY wr1-oaque-bundle-key},
  ...
}

-- Entity secret key schemes
--------------------------------------------------------------------------------
entity-secret-key-scheme OBJECT IDENTIFIER ::= { wave-id 14 }
ed25519-secret-id OBJECT IDENTIFIER ::= { entity-secret-key-scheme 1 }
curve25519-secret-id OBJECT IDENTIFIER ::= { entity-secret-key-scheme 2 }
-- 3 through 6 for deprecanted BN256
oaque-BLS12381-s20-private-key-id OBJECT IDENTIFIER ::= { entity-secret-key-scheme 7 }
oaque-BLS12381-s20-master-key-id OBJECT IDENTIFIER ::= { entity-secret-key-scheme 8 }
bls12381-ibe-master-key-id OBJECT IDENTIFIER ::= { entity-secret-key-scheme 9 }
bls12381-ibe-private-key-id OBJECT IDENTIFIER ::= { entity-secret-key-scheme 10 }
EntitySecretKeySchemes TYPE-IDENTIFIER ::= {
  {Private-Ed25519 IDENTIFIED BY ed25519-secret-id} |
  {Private-Curve25519 IDENTIFIED BY curve25519-secret-id} |
  {Private-BLS12381-OAQUE IDENTIFIED BY oaque-BLS12381-s20-private-key-id} |
  {Master-BLS12381-OAQUE IDENTIFIED BY oaque-BLS12381-s20-master-key-id} |
  {Master-BLS12381-IBE IDENTIFIED BY bls12381-ibe-master-key-id} |
  {Private-BLS12381-IBE IDENTIFIED BY bls12381-ibe-private-key-id},
  ...
}

-- Entity keyring schemes
--------------------------------------------------------------------------------
entity-keyring-scheme OBJECT IDENTIFIER ::= { wave-id 15 }
plaintext-keyring-id OBJECT IDENTIFIER ::= { entity-keyring-scheme 1 }
aes128-gcm-pbkdf2 OBJECT IDENTIFIER ::= { entity-keyring-scheme 2 }
EntityKeyringSchemes TYPE-IDENTIFIER ::= {
  {EntityKeyring IDENTIFIED BY plaintext-keyring-id} |
  {KeyringAESCiphertext IDENTIFIED BY aes128-gcm-pbkdf2},
  ...
}

-- End to end encrpytion key schemes
--------------------------------------------------------------------------------
e2ee-message-key-scheme OBJECT IDENTIFIER ::= { wave-id 16 }
e2ee-curve25519-ecdh OBJECT IDENTIFIER ::= { e2ee-message-key-scheme 1 }
e2ee-wr1 OBJECT IDENTIFIER ::= { e2ee-message-key-scheme 2 }
E2EEMessageKeySchemes TYPE-IDENTIFIER ::= {
 {MessageKeyCurve25519ECDH IDENTIFIED BY e2ee-curve25519-ecdh} |
 {MessageKeyWR1 IDENTIFIED BY e2ee-wr1},
 ...
}

-- Name declaration key schemes
--------------------------------------------------------------------------------
name-declaration-key-scheme OBJECT IDENTIFIER ::= { wave-id 17 }
name-key-wr1 OBJECT IDENTIFIER ::= { name-declaration-key-scheme 1 }
name-key-none OBJECT IDENTIFIER ::= { name-declaration-key-scheme 2 }
NameDeclarationKeySchemes TYPE-IDENTIFIER ::= {
 {NameDeclarationKeyWR1 IDENTIFIED BY name-key-wr1}|
 {NameDeclarationKeyNone IDENTIFIED BY name-key-none},
 ...
}


END
