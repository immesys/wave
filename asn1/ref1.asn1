WAVE-Reference-1 DEFINITIONS AUTOMATIC TAGS ::=
BEGIN

  IMPORTS attestation-body-scheme,
         attestation-reference-key-scheme,
         outer-signature-scheme FROM Wave-Schema;

  entity-hash-keccak-256 OBJECT IDENTIFIER ::=  { attestation-body-schemed 1 }

END
