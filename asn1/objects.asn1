Wave-Schema DEFINITIONS AUTOMATIC TAGS ::=
BEGIN

  WaveAttestation ::= SEQUENCE {
      -- this enables blind decoding of wave objects
      waveObjectVersion OBJECT IDENTIFIER,

      -- the subject of the attestation, who is receiving permissions or
      -- having a property attested to
      subject EntityHash,

      -- how this attestation revoked
      revocations SEQUENCE OF RevocationOption,

      -- extensions that are visible without any decryption of the
      -- attestation
      publicExtensions SEQUENCE OF Extension,

      -- The main content of the attestation SHOULD be encrypted using
      -- a scheme that permits provers and verifiers to decrypt it but
      -- nobody else. The result of decrypting this MUST be an
      -- AttestationBody object but depending on the context of the
      -- decryption (e.g prover vs verifier) the contents of that
      -- AttestationBody object may differ.
      body SEQUENCE {
        attestationBodyScheme OBJECT IDENTIFIER,
        parameters ANY DEFINED BY attestationBodyScheme OPTIONAL,
        value OCTET STRING
      },

      -- The attestation is signed with an ephemeral signing key generated
      -- for a single use (or another signature scheme suitable for single
      -- use is permitted). The fingerprint of this signature scheme and
      -- its parameters is put inside the AttestationBody so that if this
      -- outer layer is modified, this can be detected after decrypting the
      -- attestation, but we also do not reveal the real verifying key of
      -- the source entity except to those who can decrypt the Attestation.
      -- The Value field must be set to the algorithm's NULL value (likely
      -- a zero length string) when calculating the signature.
      outerSignature SEQUENCE {
        outerSignatureScheme OBJECT IDENTIFIER,
        parameters ANY DEFINED BY outerSignatureScheme OPTIONAL,
        value OCTET STRING
      }
  }

  -- Irrespective of the algorithm used to encrypt the body, this
  -- is the object it contains
  AttestationBody ::= SEQUENCE {
    -- These are fields that contain information that should be
    -- visible to the subject of the Attestation (and perhaps
    -- chained attestation subjects) but should not be visible to those
    -- verifying this attestation as part of a proof.
    forProver SEQUENCE {
      extensions SEQUENCE OF Extension
    },

    -- These are fields visible to both prover and verifier
    forVerifier AttestationVerifierBody

  }


  -- These are fields visible to both prover and verifier
  AttestationVerifierBody ::= SEQUENCE {
    -- the creator of the DOT
    attester EntityHash,
    -- the subject of the attestation
    subject EntityHash,
    -- the policy domain. If omitted, the policy is global. A policy domain
    -- is an Entity that represents the scope of the attestation. The exact
    -- semantics are specific to the scheme
    -- TODO then I think we should just omit this and put it inside the policy
    -- domain EntityHash OPTIONAL,

    -- when is this trust valid
    validity SEQUENCE {
      notBefore UTCTime,
      notAfter UTCTime
    },
    -- this ensures that the outer layer (plaintext fields)
    -- has not been tampered with. The fingerprint is calculated
    -- using the given algorithm over the outerSignature fields (sans the value)
    outerSignatureBinding SEQUENCE {
      outerSignatureBindingScheme OBJECT IDENTIFIER,
      parameters ANY DEFINED BY outerSignatureBindingScheme OPTIONAL,
      value OCTET STRING
    },

    -- the nature of the trust
    policy SEQUENCE {
      scheme OBJECT IDENTIFIER,
      -- DER encoding of ASN.1 value identified by scheme
      value OCTET STRING
    },

    -- extensions for use by the verifier
    extensions SEQUENCE OF Extension,

    -- signature over the ephemeral public key used for the
    -- outer signature
    innerSignature SEQUENCE {
      innerSignatureScheme OBJECT IDENTIFIER,
      parameters ANY DEFINED BY innerSignatureScheme OPTIONAL,
      value OCTET STRING
    }
  }

  Location ::= SEQUENCE {
    locationScheme OBJECT IDENTIFIER,
    value OCTET STRING
  }

  Extension ::= SEQUENCE {
    extnID OBJECT IDENTIFIER,
    critical BOOLEAN DEFAULT FALSE,
    -- DER encoding of ASN.1 value identified by extnID
    value OCTET STRING
  }
  EntityHash ::= SEQUENCE {
    entityHashScheme OBJECT IDENTIFIER,
    parameters ANY DEFINED BY entityHashScheme OPTIONAL,
    value OCTET STRING
  }
  AttestationHash ::= SEQUENCE {
    attestationHashScheme OBJECT IDENTIFIER,
    parameters ANY DEFINED BY attestationHashScheme OPTIONAL,
    value OCTET STRING
  }

  RevocationOption ::= SEQUENCE {
    revocationScheme OBJECT IDENTIFIER,
    parameters ANY DEFINED BY revocationScheme OPTIONAL,
    value OCTET STRING,
    -- If this revocation scheme is not understood, should
    -- the object be treated as revoked (TRUE) or not (FALSE)
    critical BOOLEAN DEFAULT FALSE
  }

  Entity ::= SEQUENCE {
    -- the entity object version
    waveObjectVersion OBJECT IDENTIFIER,
    -- the entity's public keys
    keys SEQUENCE OF EntityKey,
    -- when is this entity valid
    validity SEQUENCE {
      notBefore UTCTime,
      notAfter UTCTime
    },
    -- revocations
    revocations SEQUENCE OF RevocationOption,
    -- extensions
    extensions SEQUENCE OF Extension
  }

  EntityKey ::= SEQUENCE {
    entityKeyScheme OBJECT IDENTIFIER,
    parameters ANY DEFINED BY entityKeyScheme OPTIONAL,
    value OCTET STRING
  }

  -- there are different kinds of proofs, this represents just one, the
  -- explicit proof that reveals the attestations. The final authorization
  -- or truth conveyed is the union of the paths through the given set of
  -- attestations
  WaveExplicitProof ::= SEQUENCE {
    waveObjectVersion OBJECT IDENTIFIER,
    attestations SEQUENCE OF AttestationReference,
    paths SEQUENCE OF AttestationChain,
    extensions SEQUENCE OF Extension
  }

  -- this is a chain of attestations connected end-to-end
  -- that represent a path through the subset of the authorization
  -- graph given in the attestations field
  AttestationChain ::= SEQUENCE {
    path SEQUENCE OF AttestationHash
  }

  AttestationReference ::= SEQUENCE {
    -- the hash of the WaveAttestation
    hash AttestationHash,

    -- generally the attestation is put in here verbatim
    content WaveAttestation OPTIONAL,

    -- or a location is given that permits retrieving the attestation
    location Location OPTIONAL,

    -- the content will generally need some keys to decrypt
    keys SEQUENCE OF AttestationReferenceKey,

    -- for some revocation schemes, it may be necessary to submit
    -- additional information with the attestation reference that shows
    -- that the attestation is not revoked (such as a signed object by
    -- the locations in the revocation option)
    revocationChecks SEQUENCE OF RevocationCheck
  }

  AttestationReferenceKey ::= SEQUENCE {
    attestationReferenceKeyScheme OBJECT IDENTIFIER,
    parameters ANY DEFINED BY attestationReferenceKeyScheme OPTIONAL,
    value OCTET STRING
  }
  RevocationCheck ::= SEQUENCE {
    revocationScheme OBJECT IDENTIFIER,
    parameters ANY DEFINED BY revocationScheme OPTIONAL,
    value OCTET STRING
  }

  ---------------------------------------------------
  -- Universal OIDs
  ---------------------------------------------------
  wave-id OBJECT IDENTIFIER ::= { 1 3 6 1 4 1 51157 }

  wave-object-version OBJECT IDENTIFIER ::= { wave-id 2 }
    attestation-object-version OBJECT IDENTIFIER ::= { wave-object-version 1 }
      attestation-object-v1 OBJECT IDENTIFIER ::= { attestation-object-version 1 }
    entity-object-version OBJECT IDENTIFIER ::= { wave-object-version 2 }
      entity-object-v1 OBJECT IDENTIFIER ::= { entity-object-version 1 }
    explicit-proof-object-version OBJECT IDENTIFIER ::= { wave-object-version 3 }
      explicit-proof-object-v1 OBJECT IDENTIFIER ::= { explicit-proof-object-version 1 }

  attestation-body-scheme OBJECT IDENTIFIER ::= { wave-id 3 }
  attestation-reference-key-scheme OBJECT IDENTIFIER ::= { wave-id 4 }
  outer-signature-scheme OBJECT IDENTIFIER ::= { wave-id 5 }
  outer-signature-binding-scheme OBJECT IDENTIFIER ::= { wave-id 6 }
  inner-signature-scheme OBJECT IDENTIFIER ::= { wave-id 7 }
  location-scheme OBJECT IDENTIFIER ::= { wave-id 8 }
  entity-hash-scheme OBJECT IDENTIFIER ::= { wave-id 9 }
  attestation-hash-scheme OBJECT IDENTIFIER ::= { wave-id 10 }
  entity-key-scheme OBJECT IDENTIFIER ::= { wave-id 11 }

END
